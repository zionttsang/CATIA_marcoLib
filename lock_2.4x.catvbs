Language="VBSCRIPT"

Sub CATMain()

Dim distanceY
distanceY = -0.237000
Dim distanceX 
distanceX =  2.400000

Dim strObjs(4)

strObjs(0) = "零件几何体"
strObjs(1) = "基座"
strObjs(2) = "胶黏剂"
strObjs(3) = "橡胶垫"
strObjs(4) = "插针"

Set partDocument1 = CATIA.ActiveDocument

Set part1 = partDocument1.Part

Set bodies1 = part1.Bodies

For i = 0 to 4

	If (0=0) Then

		Set body1 = bodies1.Item(strObjs(i))
		
		part1.InWorkObject = body1
		
		Set hybridShapeFactory1 = part1.HybridShapeFactory

		Set hybridShapeDirection1 = hybridShapeFactory1.AddNewDirectionByCoord(1.000000, 0.000000, 0.000000)

		Set shapeFactory1 = part1.ShapeFactory

		Set translate1 = shapeFactory1.AddNewTranslate2(distanceX)

		Set hybridShapeTranslate1 = translate1.HybridShape

		hybridShapeTranslate1.VectorType = 0

		hybridShapeTranslate1.Direction = hybridShapeDirection1

		part1.InWorkObject = hybridShapeTranslate1

		part1.Update
	
	End If
	
Next

End Sub
